(defun c:mcpdraw ()
  (setvar "CMDECHO" 0)
  (command "_COLOR" 1)
  (command "_LINE" "0,0,0" "100,0,0" "")
  (command "_COLOR" 2)
  (command "_LINE" "100,0,0" "100,100,0" "")
  (command "_COLOR" 3)
  (command "_LINE" "100,100,0" "0,100,0" "")
  (command "_COLOR" 4)
  (command "_LINE" "0,100,0" "0,0,0" "")
  (command "_COLOR" 5)
  (command "_LINE" "0,0,0" "100,100,0" "")
  (command "_COLOR" 6)
  (command "_LINE" "100,0,0" "0,100,0" "")
  (command "_COLOR" 1)
  (command "_TEXT" "0,-15,0" "5.0" "0" "MCP AUTOCAD 2022 - COMPLETED!")
  (command "_ZOOM" "_E")
  (princ "\nSuccessfully drew geometry via AutoLISP!")
  (princ)
)
(c:mcpdraw)
